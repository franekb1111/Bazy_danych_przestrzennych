FME workspace shapefile2none.fmw
Startup Python:
      import smtplib, ssl
      from datetime import datetime

      port = 465  # For SSL
      password = FME_MacroValues['HASLO']

      sender_email = FME_MacroValues['EMAIL']
      receiver_email = FME_MacroValues['EMAIL_KLIENTA']
      nazwa_gm = FME_MacroValues['NAZWA_POWIATU']

      current_datetime = datetime.now().strftime("%H:%M")

      message = f"""\
      Subject: Rozpoczęto proces

      „Drogi użytkowniku {receiver_email}, o godzinie {current_datetime} rozpoczęto przetwarzanie
      danych dla gminy: {nazwa_gm}”"""

      message = message.encode("utf-8")

      # Create a secure SSL context
      context = ssl.create_default_context()

      with smtplib.SMTP_SSL("smtp.gmail.com", port, context=context) as server:
          server.login("geoinformatyka21.22@gmail.com", password)
          server.sendmail(sender_email, receiver_email, message)
Shutdown Python:
      import smtplib, ssl
      from datetime import datetime

      port = 465  # For SSL
      password = FME_MacroValues['HASLO']

      sender_email = FME_MacroValues['EMAIL']
      receiver_email = FME_MacroValues['EMAIL_KLIENTA']

      message = f"""\
      Subject: Zakończono proces

      „Drogi użytkowniku {receiver_email}, proces się powiódł”"""

      message = message.encode("utf-8")

      # Create a secure SSL context
      context = ssl.create_default_context()

      with smtplib.SMTP_SSL("smtp.gmail.com", port, context=context) as server:
          server.login("geoinformatyka21.22@gmail.com", password)
          server.sendmail(sender_email, receiver_email, message)

Parameters:
- EMAIL = geoinformatyka21.22@gmail.com   # E-mail
- DATA_KONCOWA = 20230822000000   # Podaj datę końcową
- EMAIL_KLIENTA = geoinformatyka21.22@gmail.com   # Podaj e-mail klineta
- HASLO =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   # Podaj hasło
- DATA_POCZATKOWA = 20230801000000   # Podaj datę początkową
- NAZWA_POWIATU = powiat wielicki   # Nazwa powiatu
- SourceDataset_SHAPEFILE = $(FME_MF_DIR)granice_pow\A02_Granice_powiatow.shp   # Source Esri Shapefile(s)
- MAX_POKRYCIE_CHM = 10   # Podaj max pokrycie chmurami
- DestDataset_TIFF = C:\Users\franekb1111\OneDrive\Pulpit\Bazy danych przestrzennych\cwiczenia_10   # Destination TIFF (Tagged Image File Format) Folder

Readers:
- SHAPEFILE_1: SHAPEFILE from $(SourceDataset_SHAPEFILE)

Writers:
- TIFF_1: TIFF to $(DestDataset_TIFF)

A02_Granice_powiatow (reader SHAPEFILE_1)
    attributes: JPT_SJR_KO varchar(3), JPT_POWIER double, JPT_KOD_JE varchar(20), JPT_NAZWA_ varchar(128), JPT_ORGAN_ varchar(254), JPT_JOR_ID long, WERSJA_OD date, WERSJA_DO date, WAZNY_OD date, WAZNY_DO date, JPT_KOD__1 varchar(3), JPT_NAZWA1 varchar(3), JPT_ORGAN1 varchar(3), JPT_WAZNA_ varchar(3), ID_BUFORA_ double, ID_BUFORA1 double, ID_TECHNIC long, IIP_PRZEST varchar(20), IIP_IDENTY varchar(128), IIP_WERSJA varchar(32), JPT_KJ_IIP varchar(20), JPT_KJ_I_1 varchar(128), JPT_KJ_I_2 varchar(32), JPT_OPIS varchar(254), JPT_SPS_KO varchar(3), ID_BUFOR_1 long, JPT_ID long, JPT_POWI_1 double, JPT_KJ_I_3 varchar(3), JPT_GEOMET double,
      JPT_GEOM_1 double, Shape_Leng double, Shape_Area double, REGON varchar(254)
    -> TestFilter
TestFilter
    DEFAULT_VALUE = <UNFILTERED>
    PASSED_TEST_GROUP_OUTPUT = FIRST
    TEST_LIST = "BOOL_OP,OR,COMPOSITE_TEST,""""""1"""""",TEST_CLAUSE,TEST $(NAZWA_POWIATU) = @Value(JPT_NAZWA_)",__NAZWA_POWIATU_ = @Value(JPT_NAZWA_)
    __NAZWA_POWIATU_ = @Value(JPT_NAZWA_) -> Clipper [CLIPPER]
    __NAZWA_POWIATU_ = @Value(JPT_NAZWA_) -> BoundingBoxAccumulator
BoundingBoxAccumulator
    ACCUM_ATTRS_NAME = Use Attributes From One Feature
    BOUNDING_BOX -> EarthCacheConnector
EarthCacheConnector
    api_key =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
    end_date = $(DATA_KONCOWA)
    interval = 7
    min_aoi_coverage_percentage = $(MAX_POKRYCIE_CHM)
    output_id = c31c1bea-a4be-11e7-8650-3ae5c7149ea7
    pipeline_name = pipeline4
    start_date = $(DATA_POCZATKOWA)
    -> Sampler
    <Rejected> -> Terminator_2
Sampler
    RATE = 1
    SAMPLE_MODE = No
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> TestFilter_3
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(_band_index) = 3",B04,"BOOL_OP,OR,COMPOSITE_TEST,""""""1"""""",TEST_CLAUSE,CASE_INSENSITIVE_TEST @Value(_band_index) = 7",B08
    B04 -> NDVICalculator_2 [Red]
    B08 -> NDVICalculator_2 [Infrared]
NDVICalculator_2
    COLORIZE = No Colorization
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator_2
    INSIDE -> ndvi (writer TIFF_1)
RasterStatisticsCalculator_2
    RASTER_LEVEL = BAND_ONLY
    RASTER_STATS = "0   MEAN   STDEV   "
    -> Inspector_3
Inspector_3
ndvi (writer TIFF_1)
    attributes: JPT_SJR_KO char(3), JPT_POWIER float, JPT_KOD_JE char(20), JPT_NAZWA_ char(128), JPT_ORGAN_ char(254), JPT_JOR_ID integer, WERSJA_OD date, WERSJA_DO date, WAZNY_OD date, WAZNY_DO date, JPT_KOD__1 char(3), JPT_NAZWA1 char(3), JPT_ORGAN1 char(3), JPT_WAZNA_ char(3), ID_BUFORA_ float, ID_BUFORA1 float, ID_TECHNIC integer, IIP_PRZEST char(20), IIP_IDENTY char(128), IIP_WERSJA char(32), JPT_KJ_IIP char(20), JPT_KJ_I_1 char(128), JPT_KJ_I_2 char(32), JPT_OPIS char(254), JPT_SPS_KO char(3), ID_BUFOR_1 integer, JPT_ID integer, JPT_POWI_1 float, JPT_KJ_I_3 char(3), JPT_GEOMET float,
      JPT_GEOM_1 float, Shape_Leng float, Shape_Area float, REGON char(254)
Terminator_2
    MESSAGE = Translation Terminated
