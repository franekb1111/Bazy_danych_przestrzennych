FME workspace shapefile_geotiff2none.fmw

Parameters:
- SourceDataset_SHAPEFILE = $(FME_MF_DIR)Supplementary_Ceremonial\Boundary-line-ceremonial-counties_region.shp   # Source Esri Shapefile(s)
- SourceDataset_GEOTIFF = $(FME_MF_DIR)data\*.tif   # Source GeoTIFF File(s) or URL(s)
- DestDataset_POSTGIS_RASTER = cw9   # Connection

Readers:
- SHAPEFILE_1: SHAPEFILE from $(SourceDataset_SHAPEFILE)
- GEOTIFF_1: GEOTIFF from $(SourceDataset_GEOTIFF)

Writers:
- POSTGIS_RASTER_1: POSTGIS_RASTER to $(DestDataset_POSTGIS_RASTER)

Boundary-line-ceremonial-counties_region (reader SHAPEFILE_1)
    attributes: NAME varchar(100), DESCRIPTIO varchar(50)
    -> AttributeFilter
AttributeFilter
    ATTR_NAME = NAME
    ATTR_VALUES = <Empty>,<Missing>,<Null>,<Unfiltered>,Gwent,South Glamorgan,Mid Glamorgan,West Glamorgan
    Gwent -> SpatialFilter [Filter]
    Gwent -> Dissolver
    South Glamorgan -> SpatialFilter [Filter]
    South Glamorgan -> Dissolver
    Mid Glamorgan -> SpatialFilter [Filter]
    Mid Glamorgan -> Dissolver
    West Glamorgan -> SpatialFilter [Filter]
    West Glamorgan -> Dissolver
Dissolver
    ACCUM_INPUT_ATTRS = Use Attributes From One Feature
    CLEANING_TOLERANCE = Automatic
    CONNECT_Z_MODE = First Wins
    DEAGGREGATE_INPUT = Yes
    AREA -> Clipper [CLIPPER]
GEOTIFF (reader GEOTIFF_1)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteRemover
RasterPaletteRemover
    -> Exports (writer POSTGIS_RASTER_1)
Exports (writer POSTGIS_RASTER_1)
